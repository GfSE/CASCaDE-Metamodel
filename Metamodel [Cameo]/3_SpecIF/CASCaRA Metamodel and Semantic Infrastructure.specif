# CASCaRA Metamodel and Semantic Infrastructure
A set of SpecIF Classes derived from a SpecIF Ontology for the domains SpecIF:DomainBase, SpecIF:DomainSystemsEngineering, SpecIF:DomainSystemModelIntegration.
- Rights: Creative Commons 4.0 CC BY-SA, https://creativecommons.org/licenses/by-sa/4.0/

## CASCaRA Metamodel and Semantic Infrastructure (SpecIF:Heading)
- dcterms:description: This model is authored with [NoMagic Cameo Systems Modeler](https://www.3ds.com/products/catia/no-magic/cameo-systems-modeler) using UML notation, then transformed to [SpecIF](https://specif.de) via Cameo XMI file and finally transformed to HTML or DOCX.
- dcterms:type: uml:Model

## CASCaRA Metamodel (uml:Package)
- dcterms:type: uml:Package
- dcterms:description: ## Design goals
  - **Separated syntax and semantics**: The metamodel governs the graph pattern independently of the ontology. Any software depends on the metamodel and doesn’t need change, when the ontology evolves over time.
  - **Interoperability**: A graph pattern is designed which may be represented in RDF, JSON-LD, GQL and OOP alike. Bidirectional transformations between any of those formats shall be possible without data-loss. Admittedly this ‘sweet-spot’ reduces expressivity when compared with any of the listed data formats, but the choice of implementation technologies is maximized. Verification and validation will show that the expressivity of the CASCaRA Graph is sufficient for the purpose.
  - **Federated data-spaces**: The general use of URIs (or UUIDs with namespace) as identifier like RDF allows linked data to reside in multiple internet servers and still form a valid graph which can be seamlessly traversed and queried.
  - **Standard queries**: The same queries shall be applicable, no matter where the data came from originally.

## CASCaRA Metamodel Diagram (cas:View)
- dcterms:description: The CASCaRA metamodel is a 'platform independent model' (PIM) in OMG terms and defines both the CADSCaRA types (above the dashed line) and the CASCaRA instances (below the dashed line), forming the CASCaRA Product Information Graph in the application domain. CASCaRA types are owl:Class and CASCaRA instances are owl:NamedIndividual.  In the specification and implementation domain, both CASCaRA types and instances are application data which are modeled as UML classes:
  - [[Entity]] and [[anEntity]] are type and instance used for model elements, such as a requirement, a function or a system component. 
  - [[Relationship]] and [[aRelationship]] are type and instance used for relations between elements, such as a 'component satisfies a requirement'. A Relationship type may define a set of [[Entity]] or [[Relationship]] types, whose instances are eligible as source or target of aRelationship instance which is thus always directed.
  - Employing enumeratedProperty, every [[Entity]] and [[Relationship]] can define a set of [[Property]], each of which specifies a datatype and range. For example, a requirement might have two 'native' properties „title“ and „description“ plus two configurable properties such as "Category" with datatype xs:string and a maximum length of 32 and „Priority“ with a single value of the [[Enumeration]] ['high', 'medium', 'low']“.
  - A datatype may be any of those known from XML. As described above, some parameters of [[Property]] may restrict the value range, such as minimum and/or maximum value of a  number, a string length or a set of enumerated values is defined by an [[Enumeration]]. 
  - [[anEntity]] or [[aRelationship]] is thus an instance of [[Entity]] or [[Relationship]] respectively. Each instance usually has a set of [[aProperty]] corresponding with the [[Property]] of its type.
  - [[aPackage]] is an instance of [[Entity]] and contains a subgraph of the global CASCaRA Graph. [[aPackage]] may have a set of [[aProperty]] corresponding with the [[Property]] of its type. Finally, aPackage can be nested.

  ### Note
  - "Technical" super-class and sub-class in the UML sense are defined in this metamodel by means of UML:Generalization.
  - "Semantic" super-type and sub-type representing types of real world instances are specified by the UML associations with an end 'specializes'.
  - As usual, the UML classes with white background and italic name are abstract.

  ## Constraints
  All constraints must be satisfied in addition to the JSON-LD schemata, XML schemata or RDF shapes.

  ### General
  - IDs are unique

  ### Model Integrity
  - Property.type is owl:DatatypeProperty
  - Property.specializes is a Property
  - Property.datatype is a valid xs: datatype
  - Property.maxLength is >0 and only specified, if datatype is xs:string
  - Property.pattern is a regular expression and only specified, if datatype is xs:string
  - Property.minInclusive is only specified, if datatype is a number
  - Property.maxInclusive is only specified, if datatype is a number
  - Property.minInclusive is smaller or equal Property.maxInclusive
  - Property datatype and range must be a super-set of those defined in the specialized Property (following the restrictions of OWL)
  - Property.defaultValue meets datatype and range
  - Property.composes entries are each pointing to a Property
  - Property.composes chain is a tree (without cyclic dependency)
  - Link.type is owl:ObjectProperty
  - Link.specializes is a Link
  - Link.enumeratedEndpoint entries point to either 1 Enumeration, 1..n Entities *or* 1..n Relationships
  - Link.defaultValue is a valid Id-string (URI or UUID with namespace)
  - Link.enumeratedEndpoints must be a super-set of those defined in the specialized Link (following the restrictions of OWL)
  - Enumeration.type is owl:Class
  - Enumeration.specializes is an Enumeration
  - Enumeration.enumeratedValue complies with the datatype
  - Entity.type is owl:Class
  - Entity.specializes is an Entity
  - Entity.enumeratedProperty entries are each pointing to a Property
  - Entity.enumeratedTargetLink entries are each pointing to a Link
  - Entity.enumeratedProperty and Entity.enumeratedTargetLink entries are super-sets of those defined in the specialized Entity.
  - Relationship.type is owl:Class
  - Relationship.specializes is a Relationship
  - Relationship.enumeratedProperty entries are each pointing to a Property
  - Relationship.enumeratedSourceLink has exactly one entry pointing to a Link
  - Relationship.enumeratedTargetLink has exactly one entry pointing to a Link
  - Relationship.enumeratedProperty, Relationship.enumeratedSourceLink and Relationship.enumeratedTargetLink entries are super-sets of those defined in the specialized Relationship.
  - aProperty is contained in a parent aPackage, anEntity or aRelationship
  - aProperty.type is a Property
  - aProperty.type is contained in enumeratedProperty list of its parent's type (Entity or Relationship)
  - aProperty minCount and maxCount are met, language-aware in case of xs:string
  - aProperty.value is a multilanguage object in case of xs:string, where the language tag is set if more than 1 language is provided
  - aProperty.value is a simple value (literal) in case the datatype is other than xs:string
  - aProperty.value meets the datatype of its type
  - aProperty.composes entries are aProperty
  - aSourceLink is contained in a parent aRelationship
  - aSourceLink.type is a Link
  - aSourceLink.type is contained in the enumeratedSourceLink list of its parent's type (Relationship)
  - aSourceLink.hasEndpoint (idRef) points to an instance of an entry listed as enumeratedSourceLink of its type (Link).
  - aTargetLink is contained in a parent aPackage, anEntity or aRelationship
  - aTargetLink.type is a Link
  - aTargetLink.type is contained in enumeratedTargetLink list of its parent's type (Entity or Relationship)
  - aTargetLink.hasEndpoint (idRef) points either to an instance of an entry listed as enumeratedTargetLink of its type (Link) or to an enumeratedValue of the listed Enumeration
  - aPackage.type is an Entity
  - aPackage.context defines all namespace prefixes used in its (sub-) graph
  - anEntity.type is an Entity
  - aRelationship.type is a Relationship
  - A specializes chain is a tree (without cyclic dependency)

  ## Limitations
  - Enumerations cannot be contained in a composed Property
  - Links cannot be contained in a composed Property
  - all enumeratedEndpoints of a given Link must be of the same item type (Enumeration, Entity or Relationship)
  - Access Permissions per user role are still missing. Role names and the way how to assign permissions per metamodel item shall be included in the standard, whereas the assignment of users to user roles is left to the implementations.
- cas:Diagram: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
- dcterms:type: uml:Diagram
- cas:Notation: UML Class Diagram

## Item (SpecIF:ModelElement)
- dcterms:type: uml:Class
- dcterms:description: The super-class (in UML terms) of all CASCaRA metamodel items specifying the type of item to allow for simple schema checking and transformation.

  Details:
  - The class is abstract.

## itemType (FMC:State)
- dcterms:type: uml:Property
- dcterms:description: Denotes CASCaRA types and instances in terms of this metamodel. It must be made explicit in all representations without native reasoner, such as in object-oriented programming, JSON, JSON-LD and XML. It may be omitted in RDF/OWL, as the top of the type hierarchy shall correspond to the metamodel itemType (see [[CASCARA Semantic Infrastructure]] and the itemType can be derived with a standard OWL reasoner.

  Details:
  - Here it is modeled as a string, but in fact it is an enumerated value for each of the concrete metamodel items (represented as UML classes), thus either Enumeration, Link, Property, Entity, Relationship, aPackage, aSourceLink, aTargetLink, aProperty, anEntity or aRelationship.

## Identifiable (SpecIF:ModelElement)
- dcterms:type: uml:Class
- dcterms:description: All sub-classes of this class (in UML terms) are identifiable, means they have an identifier, a title (name) and optionally a description. 

  Details:
  - The class is abstract.
  - All attributes are inherited by its subclasses.
  - All type level items in the upper part of the diagram are commonly released and made available with an URL path including the revision. Hence, multiple revisions of a type set may exist in parallel.
  - All instance level items in the lower part of the diagram may be updated individually with change information *modified*, *revision*, *priorRevision* and *creator*. The prior revision identifier is memorized to support change history and branching. In case of a merge, there are two prior revisions.

## id (FMC:State)
- dcterms:type: uml:Property
- dcterms:description: A globally unique identifier, either a fully qualified URI or a name with namespace standing for an URI, see [[aPackage]] [[context]].

## description (FMC:State)
- dcterms:type: uml:Property
- dcterms:description: A multiLanguageText.  Maps to dcterms:description.

  Details:
  - Here a multiplicity [0..1] is given, but in fact that depends on the itemType. 
  - For all types (Enumeration, Property, Link, Entity and Relationship), a title is mandatory. 
  - In case of anEntity at least one of title or description is required, because it must be possible to represent a text paragraph as anEntity, which simply does not have a title.
  - In case of aRelationship both title and description are optional. If missing the title and/or description of the respective Relationship type applies. This avoids lots of repetition in real-world data-sets.
  - The same applies for aProperty, aSourceLink and aTargetLink; both title and description are optional.

## modified (FMC:State)
- dcterms:type: uml:Property
- dcterms:description: A ISO-8601 DateTime value recording the point in time of the last change.

## revision (FMC:State)
- dcterms:type: uml:Property
- dcterms:description: A unique string identifying the revision of the entity or relationship instance.

## priorRevision (FMC:State)
- dcterms:type: uml:Property
- dcterms:description: Links to the previous revisions of an entity or relationship instance. It is a list with 
  - zero elements, if it is the first revision,
  - one element for a subsequent revision or
  - two elements when two branches are merged.

## creator (FMC:State)
- dcterms:type: uml:Property
- dcterms:description: The person committing the last change. Is often an e-mail address.

## Element (SpecIF:ModelElement)
- dcterms:type: uml:Class
- dcterms:description: A super-class (in UML terms) of [[Entity]] (type of entities) and [[Relationship]] (type of relationships). 

  Details:
  - The class is abstract.
  - All attributes and associations are inherited by its sub-classes Entity and Relationship.
  - The globalTitle of the Elements is used to integrate the instances of a partial graphs to an overarching CASCaRA graph.
  - Best practice is to release a set of CASCaRA types (thus all sub-classes of Element) from time to time as a whole. The version id is included in the directory path, so that multiple releases can be hosted in parallel.

## title (FMC:State)
- dcterms:type: uml:Property
- dcterms:description: A multiLanguageText. Maps to dcterms:title or rdf:label.

  Details:
  - Here a multiplicity [0..1] is given, but in fact that depends on the itemType. 
  - For all types (Enumeration, Property, Link, Entity and Relationship), a title is mandatory. 
  - In case of anEntity at least one of title or description is required, because it must be possible to represent a text paragraph as anEntity, which simply does not have a title.
  - In case of aRelationship both title and description are optional. If missing, the title and/or description of the respective Relationship type applies. This avoids lots of repetition in real-world data-sets.
  - The same applies for aProperty, aSourceLink and aTargetLink; both title and description are optional and the respective properties of the type apply.

## definition (FMC:State)
- dcterms:type: uml:Property
- dcterms:description: A multiLanguageText mandatory for all types. Maps to skos:definition.

## icon (FMC:State)
- dcterms:type: uml:Property
- dcterms:description: An icon defined with a type can be used to decorate the instances.

  Example: 
  - Folders as sub-type of Organizer and thus Entity may specify a UTF-8 character 🗀 for use by folders grouping certain model-elements.
  - A data-URL is also permitted as an icon.

## color (FMC:State)
- dcterms:type: uml:Property

## globalTitle (FMC:State)
- dcterms:type: uml:Property
- dcterms:description: The title assigned by matching the title with the terms of the ontology by the 'globalize' operation.

## Enumeration (SpecIF:ModelElement)
- dcterms:type: uml:Class
- dcterms:description: A type defining a set of enumerated values, where each value has an *id* and either a multi-language *title* in case of datatype xs:string or otherwise a simple *value*.

  A corresponding [[Link]] type must be defined with an [[enumeratedEndpoint]] to this *Enumeration*. For example, anEntity 'Requirement-XYZ' has aTargetLink 'Priority' pointing to aValue 'medium' being an instance of Enumeration 'Priority-Values'.

  Details:
  - The set of enumerated values of a specialized Enumeration must be a subset of those of its super-type.
  - Enumeration is modelled as a sub-class of [[Element]], however there is no known use-case where configurable properties (*enumeratedProperty*) make sense.

## datatype (FMC:State)
- dcterms:type: uml:Property
- dcterms:description: One of the xs: data types. Shall be anyURI.

## enumeratedValue (SpecIF:ModelElement)
- dcterms:type: uml:Class
- dcterms:description: Is a defined value of an [[Enumeration]]. If present, it must have either a *title* or a *value*.

  Details:
  - In case of datatype xs:string, a *title* must be defined with one or more string values in different languages ('multiLanguageText').
  - In case of all other datatypes *value* must be a simple value. 
  - in RDF, an enumeratedValue is an individual of its Enumeration. 
  - In JSON-LD and XML, any enumeratedValue is defined as a child element of the object resp. tag representing the Enumeration.

  An instance (anEntity, aRelationship or aPackage) then has [[aTargetLink]] pointing to zero to many (0..n) enumeratedValues with [[hasEndpoint]]. The permissible number of values is defined by minCount and maxCount of the type of [[aTargetLink]].

## Entity (SpecIF:ModelElement)
- dcterms:type: uml:Class
- dcterms:description: Entity is a type of model elements, such as a system component or a requirement. An Entity is an owl:Class.

  Details:
  - Entity should have a title (name) and may have a description (definition).
  - Entity may specify (configure) zero to many types of properties its instances may have. 
  - The definitions of the entity together with those of the properties may be used to build user dialogs with input verification as well as to check its instances whether all property values have a correct type and value range as well as whether all required ones are present.

## Relationship (SpecIF:ModelElement)
- dcterms:type: uml:Class
- dcterms:description: A type of relationships between two entities to allow assertions such as 'a system component satisfies a requirement'. All relationships are bilateral and directed. This allows for statements according to propositional logic. They can be easily mapped to many technologies such as RDF or even ReqIF. Being reified, a Relationship is an owl:Class.

  Details:
  - Relationship must have a title (name) and may have a description (definition).
  - Relationship lists zero to many property types its instances may have.
  - Relationship may define (configure) entitiy types or relationship types, whose instances are eligible as source resp. target in a relationship. If none are defined, all entities and relationships are eligible.
  - Relationship is reified (as a rdfs:Resource in RDF), so that it can be a source or target of another Relationship - to make a statement on a statement.
  - The definitions of a relationship together with those of their properties may be used to build user dialogs with input verfication and to check its instances whether all properties have a correct type and value range as well as whether all required ones are present.

## globalReversed (FMC:State)
- dcterms:type: uml:Property
- dcterms:description: If set, the instances of the Relationship are interpreted in reverse direction when evaluated in the global graph.

  Example:
  - If the ontology defines a term 'satisfies', an incoming relationship named 'satisfied-by' is reversed and the globalTitle is set to 'satisfies' and globalReversed is set to 'true'.

## Configurable (SpecIF:ModelElement)
- dcterms:type: uml:Class
- dcterms:description: Besides 'native' properties which are defined by the metamodel (such as title and description), an [[Element]] can have configurable properties and links. Those configurable properties and links support a dynamic data model, so that the ontology can evolve over time without software change. Additional detail such as data type and range can be provided to build dynamic forms, for example. It is in fact the core feature to separate CASCaRA syntax and semantics.

  Details:
  - This class is abstract.

## minCount (FMC:State)
- dcterms:type: uml:Property
- dcterms:description: The minimum count of a 'configurable' defined by an [[Element]] type for its instances. Thus [[anElement]] owning [[aProperty]] or [[aLink]] must have at least this number of occurrences. Is '0' by default.

  For example, if a property type 'Priority' has a minCount=1 and a requirement type specifies an enumeratedProperty 'Priority', a requirement instance must have at least one property of type Priority (with a value).

## maxCount (FMC:State)
- dcterms:type: uml:Property
- dcterms:description: The maximum count of a 'configurable' defined by an [[Element]] type for its instances. Thus  [[anElement]] owning [[aProperty]] or [[aLink]] must have at most this number of occurrences. Is '0' by default.

  For example, if a property type 'Priority' has a maxCount=1 and a requirement type specifies an enumeratedProperty 'Priority', a requirement instance must have no more than one property of type Priority (with a value).

## defaultValue (FMC:State)
- dcterms:type: uml:Property
- dcterms:description: Optional default value(s) in case an Element's property does not have an individual value when instantiated.  It may be changed later on, unless readOnly is set, and must follow the definitions of the Property type resp. Link type at all times, of course.

  Details:
  - In case of Link, the value must be an identifier of Enumeration, Entity or Relationship.
  - In case of Property, a value of the datatype as specified must be asserted.
  - If the datatype is string, the value is a language string consisting of value and IETF language tag ('multiLangueText').
  - Otherwise the value is a simple value.
  - Values of all datatypes are represented as a string in all data formats, even JSON and JSON-LD.
  - In the reference implementation, there is no difference in the instance's value, whether taken from the defaultValue or assigned explicitly. If an explicit value is removed, the defaultValue shall be reassigned.

## readOnly (FMC:State)
- dcterms:type: uml:Property
- dcterms:description: The property value of an individual [[aPackage]], [[anEntity]] or [[aRelationship]] is assiged with the defaultValue at creation and may not be updated or deleted during the individual's lifetime. 

  For example, this feature is needed to represent SysML v2 models where constant attributes are defined at type level and assigned to all instances.

## Property (SpecIF:ModelElement)
- dcterms:type: uml:Class
- dcterms:description: Every type [[Entity]] and [[Relationship]] can have an individual set of configurable properties, each of which is uniquely defined by id (name), datatype and range. A Property is an owl:DatatypeProperty.

  Details:
  - Property type must have a title and may have a description.
  - Property type may define a minimum and maximum count of values.
  - Property type must define a datatype and may restrict its range by minInclusive, maxInclusive or or a pattern defined by Regular Expression.
  - A property type may define a default value which must of course satisfy its own data type and range.
  - Property type may be composed of multiple property types to form a structured data type (xs:complexType). The structure must be a tree, thus without cyclic dependency.

  Example: 
  - A requirement might have a configurable property, such as 'Category' with datatype xs:string with a maximum length of 32. 
  - A *Priority* with a single choice of values ['high', 'medium', 'low']“ would be defined as a [[Link]] to an [[Enumeration]].

## maxLength (FMC:State)
- dcterms:type: uml:Property
- dcterms:description: Maximum length of a property value with datatype 'xs:string'. Is not allowed with any other datatype.

## minInclusive (FMC:State)
- dcterms:type: uml:Property
- dcterms:description: The minimum value a property of this type may have. May be applied only for numeric datatypes.  It the intrinsic minimum value of the datatype by default.

## maxInclusive (FMC:State)
- dcterms:type: uml:Property
- dcterms:description: The maximum value a property of this type may have. May be applied only for numeric datatypes. It the intrinsic maximum value of the datatype by default.

## pattern (FMC:State)
- dcterms:type: uml:Property
- dcterms:description: A Regular Expression that must evaluate successfully with the property value. Can also be used to limit the number of decimals of a number, as there is no restriction like xs:fractionDigits in SHACL.

## Link (SpecIF:ModelElement)
- dcterms:type: uml:Class
- dcterms:description: Is an identifiable link type. It is used as a named connector between a reified [[Relationship]] and its source and target, or as a named connector between an [[Entity]] and a directly related target. A Link is an owl:ObjectProperty.

  Details:
  - A link type can be specialized by another. For example the most global 'linksTarget' may be specialized by 'depicts'.
  - If *revisionAware* is set for a Link, each endpoint of its instances is deleted as soon as the referenced endpoint itself is updated.

  Examples: 
  - An Organizer (semantic sub-type of [[Entity]]) may list Requirements (another semantic sub-type of Entity) to construct a document outline. As such the Link type *lists* is specified as enumeratedTargetLink by Organizer.
  - An [[Entity]] Requirement might have a property with enumerated values ['high', 'medium' or 'low']. This is represented by a Link type pointing to an [[Enumeration]] defining those values.

## revisionAware (FMC:State)
- dcterms:type: uml:Property
- dcterms:description: Indicates whether an instance of this type is valid for a *specific* or *any* revision of the specified endpoints. 

  Details:
  - If *revisionAware* is set, all references occurring as endpoint of its instances are deleted as soon as the endpoint itself is updated; otherwise they are preserved.
  - In rare cases only one of a [[Relationship]]'s [[enumeratedSourceLink]] or [[enumeratedTargetLink]] can be 'revisionAware'.

  Examples:
  - [[aLink]] named *lists* of an outline (folder) shall continue to reference an endpoint, even if updated. So *revisionAware* of its [[Link]] type is omitted or set to 'false'.
  - [[aRelationship]] named *verifies* shall apply between specific revisions of a *test-case* and a *requirement*. So the types of both [[aSourceLink]] and [[aTargetLink]] set *revisionAware* to 'true'. If the *requirement* is updated, it has no more *verifies* relationship, until explicitly set after repeating the *test-case*.

## anElement (SpecIF:ModelElement)
- dcterms:type: uml:Class
- dcterms:description: A super-class (in UML terms) of [[anEntity]] and [[aRelationship]]. 

  Details:
  - The class is abstract.
  - All attributes and associations are inherited by its sub-classes.

## anEntity (SpecIF:ModelElement)
- dcterms:type: uml:Class
- dcterms:description: Is used for instances of model-elements such as a system component or a requirement. Is project data ('payload') having a clear meaning through its type [[Entity]].

  Details:
  - anEntity must have either a title or a description - or both. This allows to compose documents including text paragraphs without title. 
  - anEntity's type enumerates the types of [[aProperty]] it may have.
  - anEntity's type also enumerates the types of [[aTargetLink]] it may have.

## aRelationship (SpecIF:ModelElement)
- dcterms:type: uml:Class
- dcterms:description: Is used for relations between entities, such as a 'system component satisfies a requirement'. All relationships are bilateral and directed. Is project data ('payload') having a clear meaning through its type [[Relationship]].

  Details:
  - This is a reified graph edge and must have exactly one [[aSourceLink]] and [[aTargetLink]] each. 
  - aRelationship is deleted, if either its aSourceLink or its aTargetsLink is deleted.
  - Its aSourceLink and its aTargetLink must have a type listed as [[enumeratedSourceLink]] resp. [[enumeratedTargetLink]] by its type [[Relationship]].
  - Similarly, its type enumerates the types of [[aProperty]] it may have.
  - Even though aRelationship may have an individual title, it is advised to omit it and assume its type's title to assure that relationships of the same type are named equally.

## aPackage (SpecIF:ModelElement)
- dcterms:type: uml:Class
- dcterms:description: A container for any selection of identifiable metamodel items. Standardized and addressable types can be omitted from aPackage. aPackage may contain specific types (from organization or project ontologies) plus the instances of interest.

  Details:
  - The type of aPackage is formally [[Entity]], but should be a sub-type of Organizer (see [[CASCaRA Semantic Infrastructure]]).
  - aPackage can be nested, as it is itself an identifiable metamodel item and can hence be part of the [[graph]] of one or more parent aPackage.
  - Additional properties such as *license* or *contributor* are defined as an enumeratedProperty in its type Package.

## context (FMC:State)
- dcterms:type: uml:Property
- dcterms:description: A list of IRIs per namespace abbreviation. Used as sequence of @prefix in RDF/Turtle, sequence of xmlns: in XML and @context in JSON-LD.

## aProperty (SpecIF:ModelElement)
- dcterms:type: uml:Class
- dcterms:description: Each property belongs to a single [[anEntity]], [[aRelationship]] or [[aPackage]]. A property has *no* identifier, thus a property update results in a new revision of the item to which it belongs. Is project data ('payload') having a clear meaning, datatype and range through its type [[Property]].

  Details:
  - aProperty may be required or not depending on the attributes minCount and maxCount of its type, but an existing property must have a value.
  - aProperty value can be mutated.
  - aProperty value cannot be deleted, the whole aProperty must be deleted, if so desired.
  - the value of aProperty must conform with the datatype, length, minInclusive, maxInclusive or pattern of its type [[Property]]. Not all restrictions apply for all datatypes.
  - aProperty may be composed of multiple aProperties to form a structured data set according to its type.

## value (FMC:State)
- dcterms:type: uml:Property
- dcterms:description: The value of a [[aProperty]].

  Details:
  - If the datatype of the property's type is string, the value is a language string consisting of value and IETF language tag ('multiLangueText'). If there is a value in only one language, the language tag is optional.
  - Some convention is needed when a string is an expression - out of scope at present.
  - Otherwise the value is a simple value.
  - The rules of XML Schema apply, for example value compatibility: "99"^^xsd:integer  = "99.0"^^xsd:decimal.

## aLink (SpecIF:ModelElement)
- dcterms:type: uml:Class
- dcterms:description: Is a super-class (in UML terms) for link instances [[aSourceLink]] and [[aTargetLink]].

  Details:
  - The class is abstract.
  - aLink may have multiple enumerated endpoints (references).
  - If its type [[Link]] is set to *revisionAware*, the enumeratedEndpoint is deleted, if the endpoint itself is updated.
  - If its type [[Link]] is not set to *revisionAware*, the enumeratedEndpoint remains, if the endpoint itself is updated.
  - The enumeratedEndpoint is deleted, if the endpoint itself is deleted.
  - aLink is deleted, if it has no more enumeratedEndpoints.

## aSourceLink (SpecIF:ModelElement)
- dcterms:type: uml:Class
- dcterms:description: A link instance serving as source for a reified [[aRelationship]]. aSourceLink has *no* identifier, thus a property update results in a new revision of the item to which it belongs. 

  From a semantic point of view, there is no need to make a distinction between aSourceLink and aTargetLink at the metamodel level. The distinction can be done and *is made* at ontology level in the [[CASCaRA Semantic Infrastructure]]. However it is much easier to check the pattern/schema/shape and to ingest data, if the itemType makes the distinction.

  Details:
  - aSourceLink may be required or not depending on the attributes minCount and maxCount of its type, but an existing one must have a value.

  Example: 
  - A relationship 'worksFor' can relate an organization instance (target) to one or multiple person instances using [[aSourceLink]] named 'Employee'.

## aTargetLink (SpecIF:ModelElement)
- dcterms:type: uml:Class
- dcterms:description: A link instance pointing to the target of a reified [[aRelationship]] or to one or more targets of [[anEntity]]. aTargetLink has *no* identifier, thus a property update results in a new revision of the item to which it belongs.

  From a semantic point of view, there is no need to make a distinction between aSourceLink and aTargetLink at the metamodel level. The distinction can be done and *is made* at ontology level in the [[CASCaRA Semantic Infrastructure]]. However it is much easier to check the pattern/schema/shape and to ingest data, if the itemType is explicit.

  Details:
  - aTargetLink may be required or not depending on the attributes minCount and maxCount of its type [[Link]], but an existing one must have a value.

  Examples: 
  - A relationship 'worksFor' can relate one or multiple person instances to an organization instance (target) using [[aTargetLink]] named 'Employer'.
  - An organizer (see [[CASCaRA Semantic Infrastructure]]) such as a chapter title (folder) in an outline can point to one or more contained items, be it anEntity, aRelationship or other.
  - [[anEntity]], [[aRelationship]] or [[aPackage]] may point to an [[enumeratedValue]] of an [[Enumeration]]. The value must belong to an enumeration listed by [[enumeratedTargetLink]] of its type .

## CASCaRA Semantic Infrastructure (uml:Package)
- dcterms:type: uml:Package
- dcterms:description: The CASCaRA Semantic Infrastructure complements the CASCaRA Metamodel by further sub-typing its items in the application domain. The idea is to keep the metamodel as simple as possible and add semantic precision through the semantic infrastructure.

  Let's consider the paradigm of separating syntax and semantics with the objective to shield the software from an ontology under evolution over time. In all likelihood, the CASCaRA Semantic Infrastructure will be used by software for reasons of simplicity. Therefore it is advised to treat the semantic infrastructure similarly to the metamodel: Change it seldomly and keep it downward compatible. Thus, software built assuming an older version shall not break when a new version of the metamodel or semantic infrastructure is adopted. So the semantic infrastructure can be seen as an intermediary layer between metamodel and ontology.

  Thus, an ontology for use with the CASCaRA Metamodel SHOULD sub-type the items of the CASCaRA Semantic Infrastructure.

## CASCaRA Semantic Infrastructure Diagram (cas:View)
- dcterms:description: The diagram illustrates the concept, but is by no means complete. Consult the data in CASCaRA JSON-LD, XML or TTL format to get a complete representation.
- cas:Diagram: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
- dcterms:type: uml:Diagram
- cas:Notation: UML Class Diagram

## Actor (cas:Entity)
- dcterms:type: uml:Class
- dcterms:description: An 'Actor' is a fundamental model element type representing an active entity, be it an activity, a process step, a function, a system component or a role.

## depicts (SpecIF:ModelElement)
- dcterms:type: cas:Link
- dcterms:description: A sub-type of [[Link]] for use by [[View]] to enumerate eligible [[Entity]] and/or [[Relationship]] types that can own a view (e.g. a state diagram describing the behavior of a component where the latter owns the depicting view).

## Entity (cas:Entity)
- dcterms:type: uml:Class
- dcterms:description: The semantic foundation for all Entity type definitions. Is an owl:Class.

## Enumeration (SpecIF:ModelElement)
- dcterms:type: cas:Enumeration
- dcterms:description: The semantic foundation for all Enumeration type definitions. Is an owl:Class. Has a finite list of values for Properties.

## Event (cas:Entity)
- dcterms:type: uml:Class
- dcterms:description: An 'Event' is a fundamental model element type representing a time reference, a change in condition/value or more generally a synchronization primitive.

## Link (SpecIF:ModelElement)
- dcterms:type: cas:Link
- dcterms:description: The semantic foundation for all Link type definitions. Is an owl:ObjectProperty.

## State (cas:Entity)
- dcterms:type: uml:Class
- dcterms:description: A 'State' is a fundamental model element type representing a passive entity, be it a value, a condition, an information storage or even a physical shape.

## Outline (cas:Entity)
- dcterms:type: uml:Class
- dcterms:description: A tree (hierarchical arrangement) of graph nodes (vertices) to create a reading sequence. Graph nodes may link to instances of [[Entity]] and/or [[Relationship]]. Outline is used at any level of the tree like a directory folder or universally for section, chapter and paragraph of a document.

## lists (SpecIF:ModelElement)
- dcterms:type: cas:Link
- dcterms:description: A sub-type of [[Link]] for use by [[Outline]] to enumerate eligible [[Entity]] and/or [[Relationship]] types.

## Table (cas:Entity)
- dcterms:type: uml:Class
- dcterms:description: A specialized [[Organizer]] with elements (cells) arranged two-dimensionally in columns and rows. Any element SHALL link to instances of [[Entity]] and/or [[Relationship]].

## shows (SpecIF:ModelElement)
- dcterms:type: cas:Link
- dcterms:description: A sub-type of[[Link]] for use by [[View]] to enumerate eligible [[Entity]] and/or [[Relationship]] types that are visible on a view (e.g. model-diagram).

## linksTarget (SpecIF:ModelElement)
- dcterms:type: cas:Link
- dcterms:description: A sub-type of [[Link]] for use by [[Relationship]] to enumerate eligible [[Entity]] and/or [[Relationship]] types that can serve as a target.

  Example:
  - By further specializing this type, a meaningful title can be given to a sourceLink, such as 'employer' in a 'worksFor' relationship being a specialization of [[Relationship]].

## View (cas:Entity)
- dcterms:type: uml:Class
- dcterms:description: A specialized [[Organizer]] with elements displayed in two or three dimensions such as a model-diagram, 3D visualization or pie-chart. Any element SHOULD link to instances of [[Entity]] and/or [[Relationship]].

## Tree (cas:Entity)
- dcterms:type: uml:Class
- dcterms:description: A specialized [[Organizer]] with elements (nodes) arranged in a strictly hierarchical manner. Any element SHALL link to instances of [[Entity]] and/or [[Relationship]].

## Root (cas:Entity)
- dcterms:type: uml:Class
- dcterms:description: A root type to anchor organizer structures in a data package. While a graph has no start and no end, a root instance with a subordinated organizer structure offers a way to explore the graph for a given purpose.

  Example:
  - A document outline anchored at a root element would define a document to read by auditors and perhaps another one for potential customers. 
  - When querying all instances of type Root, a list of available documents is returned.

## linksSource (SpecIF:ModelElement)
- dcterms:type: cas:Link
- dcterms:description: A sub-type of [[Link]] for use by [[Relationship]] to enumerate eligible [[Entity]] and/or [[Relationship]] types that can serve as a source.

  Example:
  - By further specializing this type, a speaking title can be given to a sourceLink, such as 'employee' in a 'worksFor' relationship being a specialization of [[Relationship]].

## Organizer (cas:Entity)
- dcterms:type: uml:Class
- dcterms:description: An Organizer is about *presenting* genuine a selection of model-elements for a given target group of users, for example a document outline, a table or a diagram.

## Relationship (cas:Relationship)
- dcterms:type: uml:Class
- dcterms:description: The semantic foundation for all Relationship type definitions. Is an owl:Class.

## Property (SpecIF:ModelElement)
- dcterms:type: cas:Property
- dcterms:description: The semantic foundation for all Property type definitions. Is an owl:DatatypeProperty.

## Package (cas:Entity)
- dcterms:type: uml:Class
- dcterms:description: A Package contains a given selection of CASCaRA items (types and instances) for a given purpose, such as a component specification for review or in a customer-supplier relationship.

## linksEnumeration (SpecIF:ModelElement)
- dcterms:type: cas:Link
- dcterms:description: A sub-type of [[Link]] for use by an [[Entity]] or [[Relationship]] to enumerate eligible [[Enumeration]] types that can serve as a target.

  Example:
  - A [[Requirement]] specifies a priority, where the priority values are defined in an [[Enumeration]] type and the link to use as linksEnumeration.
  - A meaningful link name such as 'has Priority' can be created through a sub-type of linksEnumeration.

## QuantityValue (cas:Entity)
- dcterms:type: uml:Class
- dcterms:description: A dimensioned quantity with two properties, a 'quantity' (a numeric value) and a 'unit' of measurement.

## hasQuantityValue (SpecIF:ModelElement)
- dcterms:type: cas:Link
- dcterms:description: A sub-type of [[Link]] for use by [[Actor]], [[State]] or [[Event]] to enumerate eligible [[QuantityValue]] types that can serve as a target.

## Collection (cas:Entity)
- dcterms:type: uml:Class
- dcterms:description: A 'Collection' is a logical (often conceptual) group of resources. It corresponds to a 'Group' in BPMN or a 'Grouping' in ArchiMate.
  - BPMN: An arbitrary set of objects can be defined as a Group to show that they logically belong together. Source: [BPMN Tutorial](http://www.bpmn-tool.com/en/tutorial/).
  - ArchiMate: The grouping element aggregates or composes concepts that belong together based on some common characteristic. Source: [ArchiMate® 3.2 Specification](https://pubs.opengroup.org/architecture/archimate3-doc/ch-Generic-Metamodel.html#sec-Grouping).

## CASCaRA Schemata (uml:Package)
- dcterms:type: uml:Package
- dcterms:description: Schemata are (resp. will be) made available for the native CASCaRA formats; they are 'Platform Specific Models' (PSM) in OMG terms:
  - JSON-Schema for [CASCaRA JSON-LD](https://product-information-graph.org/schema/latest/jsonld/).
  - XML-Schema (XSD) for CASCaRA XML *(in preparation)*
  - RDF *(in preparation, while it is not yet clear how to formulate the CASCaRA metamodel and its constraints in SPARQL, SHACL or other)*.

  Note: Schemata can only check the *format* of a data-set. Constraints apply in addition. Please refer to the Metamodel chapter above.

## CASCaRA Example (uml:Package)
- dcterms:type: uml:Package
- dcterms:description: A simple, yet representative CASCaRA example is presented. This chapter describes it, whereas the data is listed in the four native CASCaRA formats:
  - CASCaRA XML, see Annex A.1 or [Very Simple Model with Requirements (XML)](https://github.com/GfSE/CASCaDE-Verification-and-Validation/blob/main/Very-simple-Model-with-Requirements%20%5BFMC%20-%20SpecIF%5D/5_XML/Very%20Simple%20Model%20(FMC)%20with%20Requirements.cas.xml).
  - CASCaRA JSON-LD, see Annex A.2 or [Very Simple Model with Requirements (JSON-LD)](https://github.com/GfSE/CASCaDE-Verification-and-Validation/blob/main/Very-simple-Model-with-Requirements%20%5BFMC%20-%20SpecIF%5D/6_JSONLD/Very_Simple_Model_(FMC)_with_Requirements.cas.jsonld).
  - CASCaRA XML, see Annex A.3 or [Very Simple Model with Requirements (RDF/Turtle)](https://github.com/GfSE/CASCaDE-Verification-and-Validation/blob/main/Very-simple-Model-with-Requirements%20%5BFMC%20-%20SpecIF%5D/7_TTL/Very_Simple_Model_(FMC)_with_Requirements.cas.ttl).
  - CASCaRA Cypher, see Annex A.4 or [Very Simple Model with Requirements (Cypher)](https://github.com/GfSE/CASCaDE-Verification-and-Validation/blob/main/Very-simple-Model-with-Requirements%20%5BFMC%20-%20SpecIF%5D/4_Cypher/Very%20Simple%20Model%20(FMC)%20with%20Requirements.cypher). As soon as implementations of GQL exist, the example will be provided in that format, as well.

## Very Simple Model with Requirements (cas:View)
- dcterms:description: A sample product information graph consisting of
  - two system model entities [[FiCo Application]] and [[FiCo Data]], where FiCo stands for 'Finance and Controlling';
  - two reified system model relationships as instance of [[Writes]] and [[Reads]];
  - three requirements [[Response Time]], [[Data Volume]] and [[Consistency]];
  - three reified relationships as instance of [[Satisfies]];
  - an [[Enumeration]] with title 'Priority-Value' used by the type [[Requirement]] and its instances - which is not shown on the diagram;
  - none of the properties, types as well as instances, aren't shown on the diagram, either.
  - a diagram showing the two model entities and two model relationships;
  - a [[Hierarchy Root]] as origin of an outline consisting of four folders [[Introduction]], [[Requirements]], [[System Diagrams]] and [[Glossary]];
  - Folders and diagrams are sub-types of [[Organizer]], as they are not part of the model itself, but are creating views of that model for a specific target audience and purpose.

  Notes:
  - This graph uses types of the CASCaRA Semantic Infrastructure (visible at the left side of the diagram), but for reasons of simplicity not any types of an ontology. Anyways, an ontology type would be included as sub-type of one of the Semantic Infrastructure types and the product information as instances of those.

  Legend:
  - The types of the CASCaRA Semantic Infrastructure are colored in hues of orange.
  - The product information, thus the instances constituting the payload, are colored in hues of yellow.
  - Any box is an instance of a CASCaRA Metamodel item (UML class). where the item type is represented as a stereotype.
  - The connectors between the boxes named 'type' are Metamodel associations.
  - The other connectors in the diagram above the dashed line are a simplified notation as explained below the dashed line.
- cas:Diagram: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
- dcterms:type: uml:Diagram
- cas:Notation: UML Class Diagram

## Entity with Property having Enumerated Values (cas:View)
- dcterms:description: The diagram shows [[anEntity]] of type 'Requirement'. The requirement 'Data Volume' has a property with an enumerated value 'priorityHigh'. See the textual notation in Appendix A or in the GitHub Repository ['CASCaDE Verification and Validation'](https://github.com/GfSE/CASCaDE-Verification-and-Validation/tree/main/Very-simple-Model-with-Requirements%20%5BFMC%20-%20SpecIF%5D).
- cas:Diagram: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
- dcterms:type: uml:Diagram
- cas:Notation: UML Class Diagram

## Entity with Property (cas:View)
- dcterms:description: The diagram shows [[anEntity]] of type [[View]] being a sub-type of [[Organizer]]. The view 'FiCo Architecture Diagram' has [[aProperty]] of type 'Category' with value 'FMC Block Diagram'. See the textual notation in Appendix A or in the GitHub Repository ['CASCaDE Verification and Validation'](https://github.com/GfSE/CASCaDE-Verification-and-Validation/tree/main/Very-simple-Model-with-Requirements%20%5BFMC%20-%20SpecIF%5D).
- cas:Diagram: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
- dcterms:type: uml:Diagram
- cas:Notation: UML Class Diagram

## Direct Link and Reified Relationship (cas:View)
- dcterms:description: The diagram shows the two ways to relate CASCaRA instances:
  - A direct link is visible in the upper part: An [[Outline]] element (folder) named [[Requirements]] lists a [[Requirement]] named [[Response Time]].
  - A reified relationship of type [[Satisfies]] connects an entity [[FiCo Application]] of type [[Application Software]] with an entity [[Response Time]] of type [[Requirement]] with a source link [[satisfying]] and a target link [[satisfied]].

  Both are also shown on diagram [[Very Simple Model with Requirements]] in a greater context.
- cas:Diagram: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
- dcterms:type: uml:Diagram
- cas:Notation: UML Class Diagram

## FiCo Application (SpecIF:ModelElement)
- dcterms:type: cas:anEntity
- dcterms:description: IT-Application for Finance and Controlling.

## FiCo Data (SpecIF:ModelElement)
- dcterms:type: cas:anEntity
- dcterms:description: Finance and Controlling Data, such as cost-units per project with budget, accrued cost etc.

## Data Volume (SpecIF:ModelElement)
- dcterms:type: cas:anEntity
- dcterms:description: The data store MUST support a total volume up to 850 GB.

## Consistency (SpecIF:ModelElement)
- dcterms:type: cas:anEntity
- dcterms:description: The data store MUST be consistent at all times.

## Response Time (SpecIF:ModelElement)
- dcterms:type: cas:anEntity
- dcterms:description: The system SHOULD respond on user queries within 300 ms.

## Requirements (SpecIF:ModelElement)
- dcterms:type: cas:anEntity

## unnamed uml:Class (SpecIF:ModelElement)
- dcterms:type: cas:aRelationship

## Satisfies (cas:Relationship)
- dcterms:type: uml:Class

## Writes (cas:Relationship)
- dcterms:type: uml:Class

## Reads (cas:Relationship)
- dcterms:type: uml:Class

## FiCo Architecture Diagram (SpecIF:ModelElement)
- dcterms:type: cas:anEntity

## Hierarchy Root (SpecIF:ModelElement)
- dcterms:type: cas:anEntity

## System Diagrams (SpecIF:ModelElement)
- dcterms:type: cas:anEntity

## Introduction (SpecIF:ModelElement)
- dcterms:type: cas:anEntity

## Glossary (SpecIF:ModelElement)
- dcterms:type: cas:anEntity

## Category (SpecIF:ModelElement)
- dcterms:type: cas:Property

## FMC Block Diagram (SpecIF:ModelElement)
- dcterms:type: cas:aProperty

## unnamed uml:Class (SpecIF:ModelElement)
- dcterms:type: cas:aTargetLink

## satisfied (SpecIF:ModelElement)
- dcterms:type: cas:Link

## Priority-Value (SpecIF:ModelElement)
- dcterms:type: cas:Enumeration

## priorityHigh (SpecIF:ModelElement)
- dcterms:type: uml:Class

## Priority (SpecIF:ModelElement)
- dcterms:type: cas:Link

## Requirement (cas:Entity)
- dcterms:type: uml:Class
- dcterms:description: A 'Requirement' is a singular documented physical and functional need that a particular design, product or process must be able to perform. _(source: [Wikipedia](https://en.wikipedia.org/wiki/Requirement))_

## Database (cas:Entity)
- dcterms:type: uml:Class

## Application Software (cas:Entity)
- dcterms:type: uml:Class

## unnamed uml:Class (SpecIF:ModelElement)
- dcterms:type: cas:aSourceLink

## satisfying (SpecIF:ModelElement)
- dcterms:type: cas:Link

## Model Elements (Glossary) (SpecIF:Heading)
- dcterms:type: SpecIF:Glossary

## Statements
- CASCaRA Metamodel SpecIF:contains CASCaRA Metamodel Diagram
- CASCaRA Metamodel SpecIF:contains aProperty
- aProperty dcterms:hasPart value
- CASCaRA Metamodel SpecIF:contains aSourceLink
- CASCaRA Metamodel SpecIF:contains Identifiable
- Identifiable dcterms:hasPart id
- Identifiable dcterms:hasPart description
- Identifiable dcterms:hasPart modified
- Identifiable dcterms:hasPart revision
- Identifiable dcterms:hasPart priorRevision
- Identifiable dcterms:hasPart creator
- CASCaRA Metamodel SpecIF:contains Element
- Element dcterms:hasPart title
- Element dcterms:hasPart definition
- Element dcterms:hasPart icon
- Element dcterms:hasPart color
- Element dcterms:hasPart globalTitle
- CASCaRA Metamodel SpecIF:contains Link
- Link dcterms:hasPart revisionAware
- CASCaRA Metamodel SpecIF:contains aTargetLink
- CASCaRA Metamodel SpecIF:contains Entity
- CASCaRA Metamodel SpecIF:contains anEntity
- CASCaRA Metamodel SpecIF:contains aRelationship
- CASCaRA Metamodel SpecIF:contains Item
- Item dcterms:hasPart itemType
- CASCaRA Metamodel SpecIF:contains aLink
- CASCaRA Metamodel SpecIF:contains anElement
- anElement dcterms:hasPart title
- CASCaRA Metamodel SpecIF:contains Property
- Property dcterms:hasPart datatype
- Property dcterms:hasPart maxLength
- Property dcterms:hasPart minInclusive
- Property dcterms:hasPart maxInclusive
- Property dcterms:hasPart pattern
- CASCaRA Metamodel SpecIF:contains Relationship
- Relationship dcterms:hasPart globalReversed
- CASCaRA Metamodel SpecIF:contains Enumeration
- Enumeration dcterms:hasPart datatype
- CASCaRA Metamodel SpecIF:contains aPackage
- aPackage dcterms:hasPart context
- CASCaRA Metamodel SpecIF:contains Configurable
- Configurable dcterms:hasPart minCount
- Configurable dcterms:hasPart maxCount
- Configurable dcterms:hasPart defaultValue
- Configurable dcterms:hasPart readOnly
- Configurable dcterms:hasPart globalTitle
- CASCaRA Metamodel SpecIF:contains enumeratedValue
- anElement dcterms:hasPart aProperty
- aProperty dcterms:hasPart aProperty
- Entity SpecIF:isAssociatedWith Entity
- aLink SpecIF:isAssociatedWith Link
- Entity SpecIF:isAssociatedWith Link
- aProperty SpecIF:isAssociatedWith Property
- anEntity SpecIF:isAssociatedWith Entity
- Element SpecIF:isAssociatedWith Property
- Link SpecIF:isAssociatedWith Element
- aRelationship SpecIF:isAssociatedWith Relationship
- Relationship SpecIF:isAssociatedWith Link
- Relationship SpecIF:isAssociatedWith Relationship
- Relationship SpecIF:isAssociatedWith Link
- Property SpecIF:isAssociatedWith Property
- aRelationship dcterms:hasPart aTargetLink
- aRelationship dcterms:hasPart aSourceLink
- Link SpecIF:isAssociatedWith Link
- Enumeration SpecIF:isAssociatedWith Enumeration
- anEntity dcterms:hasPart aTargetLink
- aPackage dcterms:hasPart Identifiable
- Property SpecIF:isAssociatedWith Property
- aLink dcterms:hasPart anElement
- aTargetLink dcterms:hasPart enumeratedValue
- Enumeration dcterms:hasPart enumeratedValue
- CASCaRA Semantic Infrastructure SpecIF:contains CASCaRA Semantic Infrastructure Diagram
- CASCaRA Semantic Infrastructure SpecIF:contains depicts
- CASCaRA Semantic Infrastructure SpecIF:contains Enumeration
- CASCaRA Semantic Infrastructure SpecIF:contains Link
- CASCaRA Semantic Infrastructure SpecIF:contains lists
- CASCaRA Semantic Infrastructure SpecIF:contains shows
- CASCaRA Semantic Infrastructure SpecIF:contains linksTarget
- CASCaRA Semantic Infrastructure SpecIF:contains linksSource
- CASCaRA Semantic Infrastructure SpecIF:contains Property
- CASCaRA Semantic Infrastructure SpecIF:contains linksEnumeration
- CASCaRA Semantic Infrastructure SpecIF:contains hasQuantityValue
- depicts SpecIF:isAssociatedWith Entity
- shows SpecIF:isAssociatedWith Entity
- shows SpecIF:isAssociatedWith Relationship
- lists SpecIF:isAssociatedWith Relationship
- Relationship SpecIF:isAssociatedWith linksTarget
- Outline SpecIF:isAssociatedWith lists
- View SpecIF:isAssociatedWith shows
- lists SpecIF:isAssociatedWith Entity
- Relationship SpecIF:isAssociatedWith linksSource
- View SpecIF:isAssociatedWith depicts
- Relationship SpecIF:isAssociatedWith linksEnumeration
- linksEnumeration SpecIF:isAssociatedWith Enumeration
- Entity SpecIF:isAssociatedWith linksEnumeration
- hasQuantityValue SpecIF:isAssociatedWith QuantityValue
- Event SpecIF:isAssociatedWith hasQuantityValue
- State SpecIF:isAssociatedWith hasQuantityValue
- Actor SpecIF:isAssociatedWith hasQuantityValue
- View SpecIF:isAssociatedWith Category
- lists SpecIF:isAssociatedWith Requirement
- CASCaRA Example SpecIF:contains Very Simple Model with Requirements
- CASCaRA Example SpecIF:contains Entity with Property having Enumerated Values
- CASCaRA Example SpecIF:contains Entity with Property
- CASCaRA Example SpecIF:contains Direct Link and Reified Relationship
- CASCaRA Example SpecIF:contains FiCo Application
- CASCaRA Example SpecIF:contains FiCo Data
- CASCaRA Example SpecIF:contains Data Volume
- CASCaRA Example SpecIF:contains Consistency
- CASCaRA Example SpecIF:contains Response Time
- CASCaRA Example SpecIF:contains Requirements
- CASCaRA Example SpecIF:contains unnamed uml:Class
- CASCaRA Example SpecIF:contains FiCo Architecture Diagram
- CASCaRA Example SpecIF:contains Hierarchy Root
- CASCaRA Example SpecIF:contains System Diagrams
- CASCaRA Example SpecIF:contains Introduction
- CASCaRA Example SpecIF:contains Glossary
- CASCaRA Example SpecIF:contains Category
- CASCaRA Example SpecIF:contains FMC Block Diagram
- CASCaRA Example SpecIF:contains unnamed uml:Class
- CASCaRA Example SpecIF:contains satisfied
- CASCaRA Example SpecIF:contains Priority-Value
- CASCaRA Example SpecIF:contains priorityHigh
- CASCaRA Example SpecIF:contains linksTarget
- CASCaRA Example SpecIF:contains Priority
- CASCaRA Example SpecIF:contains unnamed uml:Class
- CASCaRA Example SpecIF:contains satisfying
- Requirements SpecIF:isAssociatedWith Outline
- Requirements SpecIF:isAssociatedWith Data Volume
- unnamed uml:Class SpecIF:isAssociatedWith Satisfies
- unnamed uml:Class SpecIF:isAssociatedWith Consistency
- unnamed uml:Class SpecIF:isAssociatedWith FiCo Data
- unnamed uml:Class SpecIF:isAssociatedWith Response Time
- unnamed uml:Class SpecIF:isAssociatedWith FiCo Application
- unnamed uml:Class SpecIF:isAssociatedWith Data Volume
- unnamed uml:Class SpecIF:isAssociatedWith Writes
- unnamed uml:Class SpecIF:isAssociatedWith Reads
- unnamed uml:Class SpecIF:isAssociatedWith FiCo Application
- unnamed uml:Class SpecIF:isAssociatedWith FiCo Data
- unnamed uml:Class SpecIF:isAssociatedWith FiCo Application
- unnamed uml:Class SpecIF:isAssociatedWith FiCo Data
- FiCo Application SpecIF:isAssociatedWith Application Software
- FiCo Data SpecIF:isAssociatedWith Database
- Requirements SpecIF:isAssociatedWith Consistency
- Requirements SpecIF:isAssociatedWith Response Time
- FiCo Architecture Diagram SpecIF:isAssociatedWith View
- FiCo Architecture Diagram SpecIF:isAssociatedWith FiCo Application
- FiCo Architecture Diagram SpecIF:isAssociatedWith FiCo Data
- Hierarchy Root SpecIF:isAssociatedWith Root
- Hierarchy Root SpecIF:isAssociatedWith Requirements
- System Diagrams SpecIF:isAssociatedWith FiCo Architecture Diagram
- Glossary SpecIF:isAssociatedWith FiCo Application
- Glossary SpecIF:isAssociatedWith FiCo Data
- Hierarchy Root SpecIF:isAssociatedWith System Diagrams
- Hierarchy Root SpecIF:isAssociatedWith Introduction
- Hierarchy Root SpecIF:isAssociatedWith Glossary
- Introduction SpecIF:isAssociatedWith Outline
- Glossary SpecIF:isAssociatedWith Outline
- System Diagrams SpecIF:isAssociatedWith Outline
- FiCo Architecture Diagram SpecIF:isAssociatedWith unnamed uml:Class
- FMC Block Diagram SpecIF:isAssociatedWith Category
- FiCo Architecture Diagram SpecIF:isAssociatedWith FMC Block Diagram
- unnamed uml:Class SpecIF:isAssociatedWith Response Time
- unnamed uml:Class SpecIF:isAssociatedWith unnamed uml:Class
- unnamed uml:Class SpecIF:isAssociatedWith satisfied
- priorityHigh SpecIF:isAssociatedWith Priority-Value
- unnamed uml:Class SpecIF:isAssociatedWith Priority
- Priority SpecIF:isAssociatedWith Priority-Value
- Data Volume SpecIF:isAssociatedWith unnamed uml:Class
- unnamed uml:Class SpecIF:isAssociatedWith priorityHigh
- Satisfies SpecIF:isAssociatedWith satisfied
- Response Time SpecIF:isAssociatedWith Requirement
- Data Volume SpecIF:isAssociatedWith Requirement
- Consistency SpecIF:isAssociatedWith Requirement
- satisfied SpecIF:isAssociatedWith Requirement
- unnamed uml:Class SpecIF:isAssociatedWith unnamed uml:Class
- unnamed uml:Class SpecIF:isAssociatedWith FiCo Application
- satisfying SpecIF:isAssociatedWith Application Software
- Satisfies SpecIF:isAssociatedWith satisfying
- unnamed uml:Class SpecIF:isAssociatedWith satisfying
- Requirements SpecIF:isAssociatedWith unnamed uml:Class
- aProperty SpecIF:isSpecializationOf Item
- aSourceLink SpecIF:isSpecializationOf aLink
- Identifiable SpecIF:isSpecializationOf Item
- Element SpecIF:isSpecializationOf Identifiable
- Link SpecIF:isSpecializationOf Configurable
- aTargetLink SpecIF:isSpecializationOf aLink
- Entity SpecIF:isSpecializationOf Element
- anEntity SpecIF:isSpecializationOf anElement
- aRelationship SpecIF:isSpecializationOf anElement
- aLink SpecIF:isSpecializationOf Item
- anElement SpecIF:isSpecializationOf Identifiable
- Property SpecIF:isSpecializationOf Configurable
- Relationship SpecIF:isSpecializationOf Element
- Enumeration SpecIF:isSpecializationOf Element
- aPackage SpecIF:isSpecializationOf anEntity
- Configurable SpecIF:isSpecializationOf Identifiable
- Actor SpecIF:isSpecializationOf Entity
- depicts SpecIF:isSpecializationOf Link
- Event SpecIF:isSpecializationOf Entity
- State SpecIF:isSpecializationOf Entity
- Outline SpecIF:isSpecializationOf Tree
- lists SpecIF:isSpecializationOf Link
- Table SpecIF:isSpecializationOf Organizer
- shows SpecIF:isSpecializationOf Link
- linksTarget SpecIF:isSpecializationOf Link
- View SpecIF:isSpecializationOf Organizer
- Tree SpecIF:isSpecializationOf Organizer
- Root SpecIF:isSpecializationOf Organizer
- linksSource SpecIF:isSpecializationOf Link
- Organizer SpecIF:isSpecializationOf Entity
- Package SpecIF:isSpecializationOf Organizer
- linksEnumeration SpecIF:isSpecializationOf Link
- QuantityValue SpecIF:isSpecializationOf Entity
- hasQuantityValue SpecIF:isSpecializationOf Link
- Collection SpecIF:isSpecializationOf Entity
- Priority SpecIF:isSpecializationOf linksTarget
- Requirement SpecIF:isSpecializationOf State
- Database SpecIF:isSpecializationOf State
- Application Software SpecIF:isSpecializationOf Actor
- CASCaRA Metamodel Diagram SpecIF:shows Link
- CASCaRA Metamodel Diagram SpecIF:shows definition
- CASCaRA Metamodel Diagram SpecIF:shows Identifiable
- CASCaRA Metamodel Diagram SpecIF:shows Configurable
- CASCaRA Metamodel Diagram SpecIF:shows Enumeration
- CASCaRA Metamodel Diagram SpecIF:shows aPackage
- CASCaRA Metamodel Diagram SpecIF:shows aLink
- CASCaRA Metamodel Diagram SpecIF:shows minInclusive
- CASCaRA Metamodel Diagram SpecIF:shows icon
- CASCaRA Metamodel Diagram SpecIF:shows creator
- CASCaRA Metamodel Diagram SpecIF:shows title
- CASCaRA Metamodel Diagram SpecIF:shows enumeratedValue
- CASCaRA Metamodel Diagram SpecIF:shows Item
- CASCaRA Metamodel Diagram SpecIF:shows aRelationship
- CASCaRA Metamodel Diagram SpecIF:shows globalTitle
- CASCaRA Metamodel Diagram SpecIF:shows Entity
- CASCaRA Metamodel Diagram SpecIF:shows minCount
- CASCaRA Metamodel Diagram SpecIF:shows anElement
- CASCaRA Metamodel Diagram SpecIF:shows datatype
- CASCaRA Metamodel Diagram SpecIF:shows id
- CASCaRA Metamodel Diagram SpecIF:shows defaultValue
- CASCaRA Metamodel Diagram SpecIF:shows value
- CASCaRA Metamodel Diagram SpecIF:shows itemType
- CASCaRA Metamodel Diagram SpecIF:shows color
- CASCaRA Metamodel Diagram SpecIF:shows Property
- CASCaRA Metamodel Diagram SpecIF:shows globalReversed
- CASCaRA Metamodel Diagram SpecIF:shows Element
- CASCaRA Metamodel Diagram SpecIF:shows maxCount
- CASCaRA Metamodel Diagram SpecIF:shows description
- CASCaRA Metamodel Diagram SpecIF:shows maxInclusive
- CASCaRA Metamodel Diagram SpecIF:shows priorRevision
- CASCaRA Metamodel Diagram SpecIF:shows modified
- CASCaRA Metamodel Diagram SpecIF:shows context
- CASCaRA Metamodel Diagram SpecIF:shows Relationship
- CASCaRA Metamodel Diagram SpecIF:shows pattern
- CASCaRA Metamodel Diagram SpecIF:shows readOnly
- CASCaRA Metamodel Diagram SpecIF:shows aTargetLink
- CASCaRA Metamodel Diagram SpecIF:shows anEntity
- CASCaRA Metamodel Diagram SpecIF:shows revisionAware
- CASCaRA Metamodel Diagram SpecIF:shows aProperty
- CASCaRA Metamodel Diagram SpecIF:shows maxLength
- CASCaRA Metamodel Diagram SpecIF:shows aSourceLink
- CASCaRA Metamodel Diagram SpecIF:shows revision
- CASCaRA Semantic Infrastructure Diagram SpecIF:shows Table
- CASCaRA Semantic Infrastructure Diagram SpecIF:shows linksTarget
- CASCaRA Semantic Infrastructure Diagram SpecIF:shows Link
- CASCaRA Semantic Infrastructure Diagram SpecIF:shows linksSource
- CASCaRA Semantic Infrastructure Diagram SpecIF:shows Root
- CASCaRA Semantic Infrastructure Diagram SpecIF:shows Actor
- CASCaRA Semantic Infrastructure Diagram SpecIF:shows View
- CASCaRA Semantic Infrastructure Diagram SpecIF:shows depicts
- CASCaRA Semantic Infrastructure Diagram SpecIF:shows lists
- CASCaRA Semantic Infrastructure Diagram SpecIF:shows Package
- CASCaRA Semantic Infrastructure Diagram SpecIF:shows Outline
- CASCaRA Semantic Infrastructure Diagram SpecIF:shows QuantityValue
- CASCaRA Semantic Infrastructure Diagram SpecIF:shows State
- CASCaRA Semantic Infrastructure Diagram SpecIF:shows Enumeration
- CASCaRA Semantic Infrastructure Diagram SpecIF:shows Relationship
- CASCaRA Semantic Infrastructure Diagram SpecIF:shows linksEnumeration
- CASCaRA Semantic Infrastructure Diagram SpecIF:shows Property
- CASCaRA Semantic Infrastructure Diagram SpecIF:shows shows
- CASCaRA Semantic Infrastructure Diagram SpecIF:shows Event
- CASCaRA Semantic Infrastructure Diagram SpecIF:shows Organizer
- CASCaRA Semantic Infrastructure Diagram SpecIF:shows Collection
- CASCaRA Semantic Infrastructure Diagram SpecIF:shows Entity
- CASCaRA Semantic Infrastructure Diagram SpecIF:shows hasQuantityValue
- CASCaRA Semantic Infrastructure Diagram SpecIF:shows Tree
- Very Simple Model with Requirements SpecIF:shows Writes
- Very Simple Model with Requirements SpecIF:shows Actor
- Very Simple Model with Requirements SpecIF:shows View
- Very Simple Model with Requirements SpecIF:shows FiCo Application
- Very Simple Model with Requirements SpecIF:shows Consistency
- Very Simple Model with Requirements SpecIF:shows unnamed uml:Class
- Very Simple Model with Requirements SpecIF:shows FiCo Data
- Very Simple Model with Requirements SpecIF:shows Requirement
- Very Simple Model with Requirements SpecIF:shows Requirements
- Very Simple Model with Requirements SpecIF:shows Satisfies
- Very Simple Model with Requirements SpecIF:shows Reads
- Very Simple Model with Requirements SpecIF:shows Introduction
- Very Simple Model with Requirements SpecIF:shows Database
- Very Simple Model with Requirements SpecIF:shows System Diagrams
- Very Simple Model with Requirements SpecIF:shows Organizer
- Very Simple Model with Requirements SpecIF:shows Response Time
- Very Simple Model with Requirements SpecIF:shows satisfied
- Very Simple Model with Requirements SpecIF:shows Glossary
- Very Simple Model with Requirements SpecIF:shows Tree
- Very Simple Model with Requirements SpecIF:shows FiCo Architecture Diagram
- Very Simple Model with Requirements SpecIF:shows Root
- Very Simple Model with Requirements SpecIF:shows Hierarchy Root
- Very Simple Model with Requirements SpecIF:shows Outline
- Very Simple Model with Requirements SpecIF:shows Application Software
- Very Simple Model with Requirements SpecIF:shows State
- Very Simple Model with Requirements SpecIF:shows Data Volume
- Very Simple Model with Requirements SpecIF:shows unnamed uml:Class
- Entity with Property having Enumerated Values SpecIF:shows Requirement
- Entity with Property having Enumerated Values SpecIF:shows unnamed uml:Class
- Entity with Property having Enumerated Values SpecIF:shows Data Volume
- Entity with Property having Enumerated Values SpecIF:shows Priority-Value
- Entity with Property having Enumerated Values SpecIF:shows priorityHigh
- Entity with Property having Enumerated Values SpecIF:shows linksTarget
- Entity with Property having Enumerated Values SpecIF:shows Priority
- Entity with Property SpecIF:shows Category
- Entity with Property SpecIF:shows View
- Entity with Property SpecIF:shows Organizer
- Entity with Property SpecIF:shows FiCo Architecture Diagram
- Entity with Property SpecIF:shows FMC Block Diagram
- Direct Link and Reified Relationship SpecIF:shows lists
- Direct Link and Reified Relationship SpecIF:shows FiCo Application
- Direct Link and Reified Relationship SpecIF:shows Outline
- Direct Link and Reified Relationship SpecIF:shows Application Software
- Direct Link and Reified Relationship SpecIF:shows Requirement
- Direct Link and Reified Relationship SpecIF:shows Requirements
- Direct Link and Reified Relationship SpecIF:shows Satisfies
- Direct Link and Reified Relationship SpecIF:shows unnamed uml:Class
- Direct Link and Reified Relationship SpecIF:shows unnamed uml:Class
- Direct Link and Reified Relationship SpecIF:shows unnamed uml:Class
- Direct Link and Reified Relationship SpecIF:shows Response Time
- Direct Link and Reified Relationship SpecIF:shows satisfied
- Direct Link and Reified Relationship SpecIF:shows satisfying
