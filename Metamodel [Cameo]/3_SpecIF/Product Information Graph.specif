# Product Information Graph
A set of SpecIF Classes derived from a SpecIF Ontology for the domains SpecIF:DomainBase, SpecIF:DomainSystemsEngineering, SpecIF:DomainSystemModelIntegration.
- Rights: Creative Commons 4.0 CC BY-SA, https://creativecommons.org/licenses/by-sa/4.0/

## Product Information Graph (SpecIF:Heading)
- dcterms:description: Author:PCUser.
  Created:01.10.2012 15:10.
  Title:.
  Comment:.
- dcterms:type: uml:Model

## Metamodel (SpecIF:View)
- dcterms:description: The metamodel is a 'platform independent model' in OMG terms and defines both the classes (top) and their instances (bottom) for the Product Information Graph (PIG):
  - [[pig:EntityClass]] and [[pig:Entity]] are used for model elements, such as a requirement, a function or a system component. 
  - [[pig:RelationshipClass]] and [[pig:Relationship]] are used for relations between entities, such as a 'system component satisfies a requirement'. A relationship class may define the classes of entities or relationships, whose instances are eligible as subject or object in a relationship.
  - [[pig:OrganizerClass]] and [[pig:Organizer]] are used for diagrams, chapters, folders or similar with links to any [[pig:ModelElement]], which is an entity or relationship. An organizer class may define the classes of entities or relationships, whose instances are eligible to be linked (i.e. organized).
  - Every [[pig:OrganizerClass]], [[pig:EntityClass]] and [[pig:RelationshipClass]] can define an individual set of [[pig:PropertyClass]]es, each of which specifies a data type. For example, a requirement might have three property classes, such as a „Title“ with data type „String of max. length 96“, a „Description“ with data type „String“ without restriction and a „Priority“ with data type „String with a single choice of ['(1) high', '(2) medium', '(3) low']“.
  - A data type may be any of those known from XML. As described above, some parameters may restrict the value range, such as minimum and/or maximum value of a  number, the number of decimals of a real number, a string length or a set of enumerated values. 
  - [[pig:Organizer]], [[pig:Entity]] or [[pig:Relationship]] is an instance of a [[pig:OrganizerClass]], [[pig:EntityClass]] or [[pig:RelationshipClass]] respectively. Each instance usually has a set of [[pig:Property]] corresponding with the [[pig:PropertyClass]]es of its class.

  Note:
  - The prefixes 'pig*', 'xs*' and 'dcterms*' designate namespaces. In other technical environments such as RDF, XML and JSON, a namespace would be separated with ':' more appropriately, which may lead to confusion in UML. The separator '*' may be replaced during transformation.
  - As usual, the classes with white background and italic name are abstract.
- SpecIF:Diagram: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
- dcterms:type: uml:Diagram
- SpecIF:Notation: UML Class Diagram

## pig:ConfigurationItem (SpecIF:ModelElement)
- dcterms:type: uml:Class
- dcterms:description: All specializations are identifiable and under revision control. 

  Details:
  - The class is abstract.
  - All attributes are inherited by its subclasses.

## pig:id (FMC:State)
- dcterms:type: uml:Property

## pig:revision (FMC:State)
- dcterms:type: uml:Property

## dcterms:modified (FMC:State)
- dcterms:type: uml:Property

## dcterms:creator (FMC:State)
- dcterms:type: uml:Property

## dcterms:title (FMC:State)
- dcterms:type: uml:Property

## dcterms:description (FMC:State)
- dcterms:type: uml:Property

## pig:ElementClass (SpecIF:ModelElement)
- dcterms:type: uml:Class
- dcterms:description: A superclass of [[pig:EntityClass]] (type of graph node), [[pig:RelationshipClass]] (type of graph edge) and [[pig:OrganizerClass]] (type of diagrams, folders etc.). Any of those classes may be selected by a [[pig:OrganizerClass]] to restrict the type of [[pig:Element]]s. Thus, a folder class may be defined allowing its instances to contain activity diagrams and activities, but not any other.

  Details:
  - The class is abstract.
  - All attributes and associations are inherited by its subclasses.

## pig:ModelElementClass (SpecIF:ModelElement)
- dcterms:type: uml:Class
- dcterms:description: A superclass of [[pig:EntityClass]] (type of graph node) and [[pig:RelationshipClass]] (type of graph edge). 

  Details:
  - The class is abstract.
  - All attributes and associations are inherited by its subclasses.

## pig:icon (FMC:State)
- dcterms:type: uml:Property

## pig:PropertyClass (SpecIF:ModelElement)
- dcterms:type: uml:Class
- dcterms:description: Every [[pig:EntityClass]], [[pig:RelationshipClass]] and [[pig:OrganizerClass]] can have an individual set of [[pig:PropertyClass]]es, each of which is uniquely defined by a data type. For example, a requirement might have three [[pig:PropertyClass]]es, such as a „Title“ with data type „String of max. length 96“, a „Description“ with data type „String of max. length 8192“ and a „Priority“ with data type „String with a single choice of ['(1) high', '(2) medium', '(3) low']“.

  Details:
  - A property class must have a title named [[dcterms:title]] and may have a description named [[dcterms:description]].
  - A property class may define a minimum and maximum count of values.
  - A property class may define default value(s) which must of course satisfy its own constraints and those of its data type.
  - A property class may be composed of multiple property classes to form a structured data type (xs:complexType). The structure must be a tree, i.e without cyclic dependency.

## sh:datatype (FMC:State)
- dcterms:type: uml:Property
- dcterms:description: One of the xs: data types.
  tbd: Use 'xs:type' instead?

## sh:minCount (FMC:State)
- dcterms:type: uml:Property
- dcterms:description: tbd: Use 'xs:minOccurs' instead?

## sh:maxCount (FMC:State)
- dcterms:type: uml:Property
- dcterms:description: tbd: Use 'xs:maxOccurs' instead?

## xs:maxLength (FMC:State)
- dcterms:type: uml:Property

## xs:minInclusive (FMC:State)
- dcterms:type: uml:Property

## xs:maxInclusive (FMC:State)
- dcterms:type: uml:Property

## xs:fractionDigits (FMC:State)
- dcterms:type: uml:Property

## xs:restriction (FMC:State)
- dcterms:type: uml:Property
- dcterms:description: tbd: Use 'sh:in' instead?

## sh:defaultValue (FMC:State)
- dcterms:type: uml:Property
- dcterms:description: Optional default value(s) in case a modelElement's property does not have an individual value. It is a list of multiple values, if maxCount is undefined or >1, or a single value otherwise.

  Here, the attribute is called 'defaultValue' for clarity and may just be called 'values' in an implementation, as all restrictions and operations of a property's values apply.

## pig:OrganizerClass (SpecIF:ModelElement)
- dcterms:type: uml:Class
- dcterms:description: [[pig:OrganizerClass]] is used for types of diagrams, chapters, folders and similar with links to any [[pig:Element]], which is an entity, relationship or organizer. 

  Details:
  - An organizer class must have a title (name) and may have a description (definition).
  - An organizer class lists one to many classes of properties its instances may have.
  - An organizer class may define the classes of entities, relationships or organizers, whose instances are eligible to be linked (i.e. organized). If none are defined, all entities, relationships and organizers are eligible.
  - The definitions of the organizer class together with those of the property classes may be used to build user dialogs and to check its instances whether all properties have a correct type and value range as well as whether all required ones are present.

## pig:EntityClass (SpecIF:ModelElement)
- dcterms:type: uml:Class
- dcterms:description: pig:EntityClass is used for types of model elements, such as a system component or a requirement.

  Details:
  - An entity should have a title (name) and may have a description (definition).
  - An entity class lists one to many classes of properties its instances may have. (No propertyClass at all is formally allowed to be consistent with other elements, but an entitiy without property has no reason to exist.)
  - The definitions of the entity class together with those of the property classes may be used to build user dialogs and to check its instances whether all properties have a correct type and value range as well as whether all required ones are present.

## pig:RelationshipClass (SpecIF:ModelElement)
- dcterms:type: uml:Class
- dcterms:description: pig:RelationshipClass is used for types of relations between two entities, such as a 'system component satisfies a requirement'. All relationships are bilateral and directed. This allows for assertions according to propositional logic. They can be easily mapped to many technologies such as RDF or ReqIF. 

  Details:
  - A relationship class must have a title (name) and may have a description (definition).
  - A relationship class lists zero to many classes of properties its instances may have.
  - A relationship class may define entitiy classes or relationship classes, whose instances are eligible as subject or object in a relationship. If none are defined, all entities and relationships are eligible.
  - The definitions of the relationship class together with those of the property classes may be used to build user dialogs and to check its instances whether all properties have a correct type and value range as well as whether all required ones are present.

## pig:Element (SpecIF:ModelElement)
- dcterms:type: uml:Class
- dcterms:description: A superclass of [[pig:ModelElement]] and [[pig:Organizer]]. Thus, an instance of pig:Organizer may be related with pig:hasElement to any instance of [[pig:Entity]], [[pig:Relationship]] or [[pig:Organizer]], as long as the related element's class is among the [[pig:OrganizerClass]]' eligible element classes.

  Details:
  - The class is abstract.

## pig:ModelElement (SpecIF:ModelElement)
- dcterms:type: uml:Class
- dcterms:description: A superclass of [[pig:Entity]] (graph node) and [[pig:Relationship]] (reified graph edge). Thus, an instance of pig:Relationship may be related to any pig:Entity or pig:Relationship with pig:hasSubject and pig:hasObject.

  Details:
  - The class is abstract.

## pig:Property (SpecIF:ModelElement)
- dcterms:type: uml:Class
- dcterms:description: Each property belongs to a single entity or relationship, wheras 
  - an entity may have 1 to many properties and 
  - a relationship may have 0 to many properties.

  Details:
  - A property must have one to many values according to the constraints of its property class and data type.
  - A property without value is omitted as a whole, as there is no need of a place-holder.
  - A property may be composed of multiple properties to form a structured data set according to its property class.

## pig:value (FMC:State)
- dcterms:type: uml:Property

## pig:Organizer (SpecIF:ModelElement)
- dcterms:type: uml:Class
- dcterms:description: [[pig:Organizer]] is used for diagrams, chapters, folders and similar with links to any [[pig:Element]], which is an entity, relationship or organizer. An organizer class may define the classes of entities, relationships or organizers, whose instances are eligible to be linked (i.e. organized).

  Details:
  - An organizer must have at least one link to an entity, relationship or organizer with a class defined in its [[pig:OrganizerClass]]. If none is defined, all entities, relationships and organizers are eligible.
  - A organizer may have zero to many properties as defined in its class.
  - The definitions of the organizer class together with those of the property classes may be used to build user dialogs and to check its instances whether all properties have a correct type and value range as well as whether all required ones are present.

## pig:Entity (SpecIF:ModelElement)
- dcterms:type: uml:Class
- dcterms:description: pig:Entity is used for model elements, such as a system component or a requirement.

  Details:
  - An entity shpuld have at least one property as properties are the only payload an entity can carry. (No property at all is formally allowed to be consistent with other elements, but an entitiy without property has no reason to exist.)
  - The entity's class lists the classes of properties it may have.
  - The definitions of the entity class together with those of the property classes may be used to build user dialogs and to check its instances whether all properties have a correct type and value range as well as whether all required ones are present.

## pig:Relationship (SpecIF:ModelElement)
- dcterms:type: uml:Class
- dcterms:description: pig:Relationship is used for relations between entities, such as a 'system component satisfies a requirement'. All relationships are bilateral and directed. This allows for assertions according to propositional logic. They can be easily mapped to many technologies such as RDF or ReqIF.

  Details:
  - A pig:Relationship is a reified graph edge and must have exactly one subject and object entity each. The subject must be an entity or relationship with a class defined by an eligible subject class of its [[pig:RelationshipClass]]. The same applies for the object.
  - A relationship may have zero to many properties as defined in its class.
  - The definitions of the relationship class together with those of the property classes may be used to build user dialogs and to check its instances whether all properties have a correct type and value range as well as whether all required ones are present.

## pig:HierarchyRoot (SpecIF:ModelElement)
- dcterms:type: uml:Class
- dcterms:description: pig:HierarchyRoot anchors hierarchies (trees) whose leaves point to a [[pig:Entity]] each. Thus, hierarchies with their items organize entities for a given target group or purpose, such as a bill of material (BoM) or a document outline. A given entity may be referenced by none, one or multiple items in one or more hierarchies.

## Model Elements (Glossary) (SpecIF:Heading)
- dcterms:type: SpecIF:Glossary

## Statements
- pig:ModelElementClass dcterms:hasPart pig:icon
- pig:PropertyClass dcterms:hasPart sh:datatype
- pig:PropertyClass dcterms:hasPart sh:minCount
- pig:PropertyClass dcterms:hasPart sh:maxCount
- pig:PropertyClass dcterms:hasPart xs:maxLength
- pig:PropertyClass dcterms:hasPart xs:minInclusive
- pig:PropertyClass dcterms:hasPart xs:maxInclusive
- pig:PropertyClass dcterms:hasPart xs:fractionDigits
- pig:PropertyClass dcterms:hasPart xs:restriction
- pig:PropertyClass dcterms:hasPart sh:defaultValue
- pig:Property dcterms:hasPart pig:value
- pig:ConfigurationItem dcterms:hasPart pig:id
- pig:ConfigurationItem dcterms:hasPart pig:revision
- pig:ConfigurationItem dcterms:hasPart dcterms:modified
- pig:ConfigurationItem dcterms:hasPart dcterms:creator
- pig:ConfigurationItem dcterms:hasPart dcterms:title
- pig:ConfigurationItem dcterms:hasPart dcterms:description
- pig:RelationshipClass SpecIF:isAssociatedWith pig:ModelElementClass
- pig:RelationshipClass SpecIF:isAssociatedWith pig:ModelElementClass
- pig:Relationship SpecIF:isAssociatedWith pig:RelationshipClass
- pig:Property SpecIF:isAssociatedWith pig:PropertyClass
- pig:Entity SpecIF:isAssociatedWith pig:EntityClass
- pig:Relationship SpecIF:isAssociatedWith pig:ModelElement
- pig:Relationship SpecIF:isAssociatedWith pig:ModelElement
- pig:PropertyClass dcterms:hasPart pig:PropertyClass
- pig:Property dcterms:hasPart pig:Property
- pig:OrganizerClass SpecIF:isAssociatedWith pig:ModelElementClass
- pig:Organizer SpecIF:isAssociatedWith pig:ModelElement
- pig:Organizer SpecIF:isAssociatedWith pig:OrganizerClass
- pig:ElementClass SpecIF:isAssociatedWith pig:PropertyClass
- pig:Element dcterms:hasPart pig:Property
- pig:Organizer dcterms:hasPart pig:Organizer
- pig:ModelElementClass SpecIF:isSpecializationOf pig:ElementClass
- pig:RelationshipClass SpecIF:isSpecializationOf pig:ModelElementClass
- pig:ModelElement SpecIF:isSpecializationOf pig:Element
- pig:Relationship SpecIF:isSpecializationOf pig:ModelElement
- pig:PropertyClass SpecIF:isSpecializationOf pig:ConfigurationItem
- pig:EntityClass SpecIF:isSpecializationOf pig:ModelElementClass
- pig:Entity SpecIF:isSpecializationOf pig:ModelElement
- pig:ElementClass SpecIF:isSpecializationOf pig:ConfigurationItem
- pig:OrganizerClass SpecIF:isSpecializationOf pig:ElementClass
- pig:Element SpecIF:isSpecializationOf pig:ConfigurationItem
- pig:Organizer SpecIF:isSpecializationOf pig:Element
- Metamodel SpecIF:shows pig:value
- Metamodel SpecIF:shows pig:ConfigurationItem
- Metamodel SpecIF:shows pig:Organizer
- Metamodel SpecIF:shows xs:fractionDigits
- Metamodel SpecIF:shows xs:minInclusive
- Metamodel SpecIF:shows sh:datatype
- Metamodel SpecIF:shows pig:PropertyClass
- Metamodel SpecIF:shows pig:ModelElementClass
- Metamodel SpecIF:shows pig:icon
- Metamodel SpecIF:shows dcterms:creator
- Metamodel SpecIF:shows pig:ElementClass
- Metamodel SpecIF:shows sh:maxCount
- Metamodel SpecIF:shows dcterms:description
- Metamodel SpecIF:shows pig:ModelElement
- Metamodel SpecIF:shows dcterms:title
- Metamodel SpecIF:shows xs:maxInclusive
- Metamodel SpecIF:shows dcterms:modified
- Metamodel SpecIF:shows pig:Relationship
- Metamodel SpecIF:shows pig:EntityClass
- Metamodel SpecIF:shows pig:RelationshipClass
- Metamodel SpecIF:shows sh:minCount
- Metamodel SpecIF:shows pig:Element
- Metamodel SpecIF:shows xs:restriction
- Metamodel SpecIF:shows pig:OrganizerClass
- Metamodel SpecIF:shows pig:Entity
- Metamodel SpecIF:shows pig:Property
- Metamodel SpecIF:shows xs:maxLength
- Metamodel SpecIF:shows pig:id
- Metamodel SpecIF:shows pig:revision
- Metamodel SpecIF:shows sh:defaultValue
